module sysrepo-module-versions {

  namespace "urn:tttech:bu-industrial:yang:sysrepo-module-versions";
  prefix sr_mod_ver;
  
  organization
    "TTTech Industrial Automation AG";
  contact
    "Web URL: support@tttech-industrial.com";
  description 
    "The proprietary YANG module for configuration managament.
    
    This custom YANG module contains the data of all implemented YANG modules with their
    names, revisions, commit ids from github, internal revisions, developer comments, ...";
    revision 2018-12-06 {
		description 
		  "The first revision.";
	}
	revision 2018-12-17 {
		description 
		  "The all objects are config false now. 
		  The leaf 'open_source_module' renamed to 'source' and his type changed to enum.";
	}
    revision 2019-09-26 {
		description 
		  "The module name changed from module-versions to sysrepo-module-versions.
		  Namespace and root container are modified according to module name changes.
		  Oraganization and conntact informations updated.";
    }
    revision 2019-12-23 {
		description 
		  "The module container sysrepo-module-versions changed to config false.";
    }
  
  container sysrepo-module-versions {
    config false;
    description
      "Modules configuration data.";
    list module {
        description 
            "The list of yang modules.";
        key "name";
            
        leaf name {
        type string;
        description
          "The name of the YANG module.";
        }
        
        leaf revision {
        type string;
        description
          "The revision of the YANG module.";
        }
        
        leaf source {
        type enumeration {
            enum github {
              description
              "The yang module is from github.";
            }
            enum fromMIB {
              description
              "The yang module is generated from MIB.";
            }
            enum proprietary {
              description
              "The yang module is TTTech proprietary module.";
            }
            enum standard_document {
              description
              "The yang module is extracted from Standards document.";
            }
        }
        description
          "This leaf represnets the source of implemented YANG module: github, generated from MIB, proprietary yang module.";
        }
        
        leaf commit_id {
        type string;
        description
          "The github commit-id of the YANG module.
          This leaf exist only if leaf 'source' has value 'github'";
        }
        
        leaf internal_version {
        type string;
        description
          "The TTTech inernal version of the YANG module.";
        }
        
        leaf-list developer_change {
        type string;
        description
          "The YANG module modifications made by developers.
          Create a new leaf for any new change.";
        }
    }
  }
}
